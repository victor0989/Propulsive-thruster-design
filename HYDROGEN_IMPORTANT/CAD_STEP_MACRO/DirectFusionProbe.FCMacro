# -*- coding: utf-8 -*-
# Macro FreeCAD: Direct Fusion Drive con TPS tipo Parker, radiadores imprimibles y módulos
# Autor: Víctor + Copilot
# Unidades: mm, eje longitudinal = X

import FreeCAD as App, FreeCADGui as Gui, Part, math

doc_name="Direct_Fusion_Drive"
if App.ActiveDocument is None or App.ActiveDocument.Label!=doc_name:
    App.newDocument(doc_name)
doc=App.ActiveDocument

# ========================
# Parámetros base DFD
# ========================
P={
    "nose_len":800.0,"nose_base_d":600.0,
    "mid_len":1400.0,"mid_d":900.0,
    "rear_len":800.0,"rear_d":1200.0,
    "hull_t":10.0,
    "cockpit_w":900.0,"cockpit_h":400.0,"cockpit_l":600.0,"cockpit_x0":600.0,
    "win_w":600.0,"win_h":250.0,"win_th":20.0,
    "win_y_off":0.5*(900.0/2.0-250.0/2.0),"win_z":0.0,
    "reactor_d":800.0,"reactor_l":900.0,"reactor_cx":2600.0,
    "ring_h":30.0,"ring_ro":420.0,"ring_ri":380.0,"ring_n":6,"ring_pitch":150.0,
    "coil_rect_w":80.0,"coil_rect_h":80.0,"coil_R":440.0,"coil_n":4,"coil_span":800.0,
    "moderator_t":100.0,"moderator_gap":20.0,"moderator_over":200.0,
    "tungsten_post_t":10.0,
    "nozzle_throat_d":300.0,"nozzle_exit_d":900.0,"nozzle_l":700.0,"nozzle_cx":2850.0,"nozzle_fillet_r":40.0,
    "truss_n":3,"truss_tube_w":80.0,"truss_R_attach":550.0,
    "tank_d":300.0,"tank_l":700.0,"tank_cx":1600.0,"tank_cy":300.0,"tank_cz":-150.0,
    "leg_L_fold":400.0,"leg_L_ext":600.0,"leg_foot_d":180.0,
    "leg_side_x1":1050.0,"leg_side_x2":1950.0,"leg_side_y":600.0,
    "leg_front_x":400.0,"leg_front_y":0.0,"leg_front_z":-(900.0/2.0)+50.0,
    "wing_root_w":600.0,"wing_tip_w":150.0,"wing_chord":450.0,
    "fin_h":400.0,"fin_base":200.0,
    "rad_panel_w":800.0,"rad_panel_h":600.0,"rad_panel_n":5
}

# ========================
# Parámetros TPS tipo Parker y radiadores imprimibles
# ========================
TPS = {
    "tps_d": 2400.0,     # diámetro escudo
    "tps_t": 100.0,      # espesor disco TPS
    "tps_gap": 120.0,    # separación morro-soporte
    "sup_L": 280.0,      # longitud soporte
    "sup_d_base": 900.0, # diámetro base soporte (hacia morro)
    "sup_d_tip": 600.0   # diámetro punta soporte (hacia TPS)
}

RAD = {
    "th": 4.0,           # espesor del radiador (sólido) para impresión y FEM
    "mount_gap_y": 30.0, # separación desde el bus en Y
    "x_start": None,     # si None, se autocalcula
    "gap_x": None        # si None, se autocalcula
}

# ========================
# Materiales (densidades y E, básicos)
# ========================
MAT = {
    'AL':     {'name':'AA-2xxx','rho':2700.0,'E':72e9,'nu':0.33,'type':'isotropic'},
    'STEEL':  {'name':'SS-304','rho':8000.0,'E':200e9,'nu':0.30,'type':'isotropic'},
    'COPPER': {'name':'Copper','rho':8960.0,'E':110e9,'nu':0.34,'type':'isotropic'},
    'CFRP':   {'name':'CFRP','rho':1550.0,'Ex':130e9,'Ey':10e9,'Ez':10e9,'nu_xy':0.25,'type':'orthotropic'},
    'CC':     {'name':'C/C TPS','rho':1600.0,'Ex':70e9,'Ey':70e9,'Ez':10e9,'nu_xy':0.2,'type':'orthotropic'}
}

# ========================
# Funciones auxiliares
# ========================
X_AXIS=App.Vector(1,0,0);Y_AXIS=App.Vector(0,1,0);Z_AXIS=App.Vector(0,0,1)

def rot_to_x():return App.Rotation(Y_AXIS,90)

def add_obj(shape,label):
    obj=doc.addObject("Part::Feature",label); obj.Shape=shape; return obj

def set_mat(obj, mat):
    if not obj: return
    m = MAT.get(mat, None) if isinstance(mat, str) else mat
    if not m: return
    obj.addProperty("App::PropertyString","Material","Meta","").Material = m.get('name','')
    obj.addProperty("App::PropertyMap","MaterialData","Meta","").MaterialData = {k:str(v) for k,v in m.items()}
    obj.addProperty("App::PropertyFloat","Density","Meta","").Density = m.get('rho',0.0)

def make_cyl_x(d,L,cx=0.0,cy=0.0,cz=0.0,label="CylX"):
    r=d/2.0;cyl=Part.makeCylinder(r,L)
    cyl.Placement=App.Placement(App.Vector(cx-L/2.0,cy,cz),rot_to_x())
    return add_obj(cyl,label)

def make_cone_x(d1,d2,L,cx=0.0,cy=0.0,cz=0.0,label="ConeX"):
    r1=d1/2.0;r2=d2/2.0;cone=Part.makeCone(r1,r2,L)
    cone.Placement=App.Placement(App.Vector(cx-L/2.0,cy,cz),rot_to_x())
    return add_obj(cone,label)

def make_torus_x(R,r,cx=0.0,cy=0.0,cz=0.0,label="TorusX"):
    tor=Part.makeTorus(R,r)
    tor.Placement=App.Placement(App.Vector(cx,cy,cz),rot_to_x())
    return add_obj(tor,label)

def make_box(w,d,h,cx=0.0,cy=0.0,cz=0.0,label="Box"):
    b=Part.makeBox(w,d,h)
    b.Placement=App.Placement(App.Vector(cx-w/2.0,cy-d/2.0,cz-h/2.0),App.Rotation())
    return add_obj(b,label)

def make_hollow_from_offset(outer_shape,t,label="Shell"):
    try:
        inner=outer_shape.makeOffsetShape(-t,0.01,join=2,fill=True)
        shell=outer_shape.cut(inner)
        return add_obj(shell,label)
    except Exception:
        return add_obj(outer_shape,label+"_fallback")

def fillet_between(shpA,shpB,r):
    fused=shpA.fuse(shpB)
    try:
        edges=[e for e in fused.Edges if e.Length>30 and e.Length<10000]
        new=fused.makeFillet(r,edges)
        return new
    except Exception:
        return fused

def sweep_rect_around_X(R,rw,rh,cx,cy,cz,ax0,ax1,label="CoilSweep"):
    circ=Part.makeCircle(R,App.Vector(cx,cy,cz),X_AXIS)
    path=Part.Wire([circ])
    p0=App.Vector(0,-rw/2.0,-rh/2.0);p1=App.Vector(0,rw/2.0,-rh/2.0)
    p2=App.Vector(0,rw/2.0,rh/2.0);p3=App.Vector(0,-rw/2.0,rh/2.0)
    e1=Part.makeLine(p0,p1);e2=Part.makeLine(p1,p2);e3=Part.makeLine(p2,p3);e4=Part.makeLine(p3,p0)
    prof=Part.Wire([e1,e2,e3,e4])
    prof.Placement=App.Placement(App.Vector(cx,cy,cz),App.Rotation(X_AXIS,0))
    sweep=Part.Wire(path).makePipeShell([prof],True,True)
    return add_obj(sweep,label)

# ========================
# Fuselaje principal
# ========================
nose=make_cone_x(P["nose_base_d"],0.0,P["nose_len"],cx=P["nose_len"]/2.0,label="Nose")
mid=make_cyl_x(P["mid_d"],P["mid_len"],cx=P["nose_len"]+P["mid_len"]/2.0,label="Mid")
rear=make_cyl_x(P["rear_d"],P["rear_len"],cx=P["nose_len"]+P["mid_len"]+P["rear_len"]/2.0,label="Rear")
fuse_fuselage_shape=nose.Shape.fuse(mid.Shape).fuse(rear.Shape)
hull=make_hollow_from_offset(fuse_fuselage_shape,P["hull_t"],label="Hull_Shell")

# ========================
# TPS tipo Parker montado en el morro
# ========================
nose_tip_x = P["nose_len"]
tps_support = make_cone_x(
    TPS["sup_d_base"], TPS["sup_d_tip"], TPS["sup_L"],
    cx = nose_tip_x + TPS["tps_gap"] + TPS["sup_L"]/2.0, cy = 0.0, cz = 0.0, label = "TPS_Support"
)
tps_disk = make_cyl_x(
    TPS["tps_d"], TPS["tps_t"],
    cx = nose_tip_x + TPS["tps_gap"] + TPS["sup_L"] + TPS["tps_t"]/2.0, cy = 0.0, cz = 0.0, label = "TPS_Shield"
)
# Fusión para pieza única imprimible
TPS_fused_shape = fillet_between(tps_support.Shape, tps_disk.Shape, r=6.0)
TPS_fused = add_obj(TPS_fused_shape, "TPS_Assembly")

# Materiales principales
set_mat(hull, 'AL'); set_mat(nose, 'AL'); set_mat(mid, 'AL'); set_mat(rear, 'AL')
set_mat(tps_support, 'STEEL'); set_mat(tps_disk, 'CC'); set_mat(TPS_fused, 'CC')

# ========================
# Ventanas y cabina
# ========================
win1=make_box(P["win_w"],P["win_th"],P["win_h"],cx=P["cockpit_x0"]+P["cockpit_l"]/2.0,cy=(P["mid_d"]/2.0)-P["win_th"]/2.0,cz=P["win_z"],label="Win_Right")
win2=make_box(P["win_w"],P["win_th"],P["win_h"],cx=P["cockpit_x0"]+P["cockpit_l"]/2.0,cy=-(P["mid_d"]/2.0)+P["win_th"]/2.0,cz=P["win_z"],label="Win_Left")
hull_cut=add_obj(hull.Shape.cut(win1.Shape).cut(win2.Shape),"Hull_Shell_Cut")

cockpit_box=Part.makeBox(P["cockpit_l"],P["cockpit_w"],P["cockpit_h"])
cockpit_box.Placement=App.Placement(App.Vector(P["cockpit_x0"],-P["cockpit_w"]/2.0,-P["cockpit_h"]/2.0),App.Rotation())
try: cockpit_f=cockpit_box.makeFillet(20.0,cockpit_box.Edges)
except Exception: cockpit_f=cockpit_box
cockpit=add_obj(cockpit_f,"Cockpit"); set_mat(cockpit,'AL')

# ========================
# Reactor, anillos y bobinas
# ========================
reactor=make_cyl_x(P["reactor_d"],P["reactor_l"],cx=P["reactor_cx"],label="ReactorCore"); set_mat(reactor,'STEEL')
rings=[]
x0=P["reactor_cx"]-P["reactor_l"]/2.0+P["ring_h"]/2.0
for i in range(P["ring_n"]):
    x=x0+i*P["ring_pitch"]
    ring=Part.makeTorus((P["ring_ro"]+P["ring_ri"])/2.0,(P["ring_ro"]-P["ring_ri"])/2.0)
    ring.Placement=App.Placement(App.Vector(x,0,0),rot_to_x())
    rings.append(ring)
rings_shape=rings[0]
for r in rings[1:]: rings_shape=rings_shape.fuse(r)
rings_obj=add_obj(rings_shape,"Reactor_Rings"); set_mat(rings_obj,'STEEL')

coils=[]
span=P["coil_span"]; cx0=P["reactor_cx"]-span/2.0
for i in range(P["coil_n"]):
    cx=cx0+i*(span/(max(1,(P["coil_n"]-1))))
    coil=sweep_rect_around_X(P["coil_R"],P["coil_rect_w"],P["coil_rect_h"],cx,0.0,0.0,0.0,0.0,label=f"Coil_{i+1}")
    coils.append(coil.Shape)
coils_shape=coils[0]
for c in coils[1:]: coils_shape=coils_shape.fuse(c)
coils_obj=add_obj(coils_shape,"Reactor_Coils"); set_mat(coils_obj,'COPPER')

# ========================
# Blindajes y tobera
# ========================
tw_len=P["tungsten_post_t"]; tw_ro=P["reactor_d"]/2.0; tw_ri=tw_ro-10.0
tw_tube=Part.makeCylinder(tw_ro,tw_len); tw_hole=Part.makeCylinder(tw_ri,tw_len+0.1)
tw_ring=tw_tube.cut(tw_hole)
tw_ring.Placement=App.Placement(App.Vector(P["reactor_cx"]+P["reactor_l"]/2.0-tw_len/2.0,0,0),rot_to_x())
tw_obj=add_obj(tw_ring,"Tungsten_Posterior"); set_mat(tw_obj,'STEEL')

noz=Part.makeCone(P["nozzle_throat_d"]/2.0,P["nozzle_exit_d"]/2.0,P["nozzle_l"])
noz.Placement=App.Placement(App.Vector(P["nozzle_cx"]-P["nozzle_l"]/2.0,0,0),rot_to_x())
noz_obj=add_obj(noz,"Magnetic_Nozzle"); set_mat(noz_obj,'STEEL')
try:
    filleted=fillet_between(rear.Shape,noz,P["nozzle_fillet_r"])
    nozzle_mount=add_obj(filleted,"Nozzle_Mount_Fillet"); set_mat(nozzle_mount,'STEEL')
except Exception:
    nozzle_mount=noz_obj

truss_list=[]
for k in range(P["truss_n"]):
    ang=k*(360.0/P["truss_n"])
    x_attach=P["nose_len"]+P["mid_len"]+P["rear_len"]-50.0
    y=P["truss_R_attach"]*math.cos(math.radians(ang))
    z=P["truss_R_attach"]*math.sin(math.radians(ang))
    L=300.0
    beam=Part.makeBox(L,P["truss_tube_w"],P["truss_tube_w"])
    beam.Placement=App.Placement(App.Vector(x_attach-L/2.0,y-P["truss_tube_w"]/2.0,z-P["truss_tube_w"]/2.0),App.Rotation())
    truss_list.append(beam)
truss_shape=truss_list[0]
for t in truss_list[1:]: truss_shape=truss_shape.fuse(t)
truss_obj=add_obj(truss_shape,"Nozzle_Truss"); set_mat(truss_obj,'STEEL')

mod_inner_r=P["reactor_d"]/2.0+P["moderator_gap"]; mod_outer_r=mod_inner_r+P["moderator_t"]
mod_len=P["reactor_l"]+P["moderator_over"]; mod_cx=P["reactor_cx"]
mod_outer=Part.makeCylinder(mod_outer_r,mod_len); mod_inner=Part.makeCylinder(mod_inner_r,mod_len+0.2)
mod_tube=mod_outer.cut(mod_inner)
mod_tube.Placement=App.Placement(App.Vector(mod_cx-mod_len/2.0,0,0),rot_to_x())
mod_obj=add_obj(mod_tube,"Shield_Moderator"); set_mat(mod_obj,'STEEL')

tn_ro=P["nozzle_exit_d"]/2.0+40.0; tn_ri=tn_ro-10.0; tn_len=20.0
tn_tube=Part.makeCylinder(tn_ro,tn_len); tn_hole=Part.makeCylinder(tn_ri,tn_len+0.1)
tn_ring=tn_tube.cut(tn_hole)
tn_ring.Placement=App.Placement(App.Vector(P["nozzle_cx"]+P["nozzle_l"]/2.0-tn_len/2.0,0,0),rot_to_x())
tn_obj=add_obj(tn_ring,"Tungsten_Nozzle_Rim"); set_mat(tn_obj,'STEEL')

# ========================
# Tanques laterales
# ========================
tank1=make_cyl_x(P["tank_d"],P["tank_l"],cx=P["tank_cx"],cy=P["tank_cy"],cz=P["tank_cz"],label="Tank_Right"); set_mat(tank1,'AL')
tank2=make_cyl_x(P["tank_d"],P["tank_l"],cx=P["tank_cx"],cy=-P["tank_cy"],cz=P["tank_cz"],label="Tank_Left"); set_mat(tank2,'AL')

# ========================
# Patas de aterrizaje
# ========================
def make_leg(x,y,z,L,d,label):
    shaft=Part.makeCylinder(d/4.0,L)
    foot=Part.makeCylinder(d/2.0,20.0)
    shaft.Placement=App.Placement(App.Vector(x-L/2.0,y,z),rot_to_x())
    foot.Placement=App.Placement(App.Vector(x+L/2.0-10.0,y,z-d/4.0),App.Rotation())
    leg=shaft.fuse(foot)
    return add_obj(leg,label)

leg_r = make_leg(P["leg_side_x1"], P["leg_side_y"], P["leg_front_z"], P["leg_L_fold"], P["leg_foot_d"], "Leg_Right_Front"); set_mat(leg_r,'STEEL')
leg_l = make_leg(P["leg_side_x1"],-P["leg_side_y"], P["leg_front_z"], P["leg_L_fold"], P["leg_foot_d"], "Leg_Left_Front"); set_mat(leg_l,'STEEL')
leg_r2= make_leg(P["leg_side_x2"], P["leg_side_y"], P["leg_front_z"], P["leg_L_fold"], P["leg_foot_d"], "Leg_Right_Rear"); set_mat(leg_r2,'STEEL')
leg_l2= make_leg(P["leg_side_x2"],-P["leg_side_y"], P["leg_front_z"], P["leg_L_fold"], P["leg_foot_d"], "Leg_Left_Rear"); set_mat(leg_l2,'STEEL')
leg_f = make_leg(P["leg_front_x"], P["leg_front_y"], P["leg_front_z"], P["leg_L_fold"], P["leg_foot_d"], "Leg_Nose"); set_mat(leg_f,'STEEL')

# ========================
# Alas / radiadores (alas sólidas tal cual)
# ========================
def make_trapezoid_wing(root_w,tip_w,chord,thickness=20.0,x0=1400.0,y0=0.0,z0=0.0,side=1,label="Wing"):
    x_le=x0; x_te=x0+chord; z_mid=z0
    p1=App.Vector(x_le,0,z_mid+root_w/2.0); p2=App.Vector(x_te,0,z_mid+root_w/2.0)
    p3=App.Vector(x_te,0,z_mid+tip_w/2.0); p4=App.Vector(x_le,0,z_mid+tip_w/2.0)
    wire=Part.makePolygon([p1,p2,p3,p4,p1]); face=Part.Face(wire)
    solid=face.extrude(App.Vector(0,side*(root_w-tip_w),0))
    slab=Part.makeBox(chord,thickness,(root_w+tip_w)/2.0)
    slab.Placement=App.Placement(App.Vector(x0,side*thickness/2.0,z0-(root_w+tip_w)/4.0),App.Rotation())
    wing=solid.common(slab)
    return add_obj(wing,label)

wing_r=make_trapezoid_wing(P["wing_root_w"],P["wing_tip_w"],P["wing_chord"],x0=P["nose_len"]+500.0,side= 1,label="Wing_Right"); set_mat(wing_r,'AL')
wing_l=make_trapezoid_wing(P["wing_root_w"],P["wing_tip_w"],P["wing_chord"],x0=P["nose_len"]+500.0,side=-1,label="Wing_Left");  set_mat(wing_l,'AL')

# ========================
# Aleta vertical
# ========================
def make_fin(h,base,thickness=20.0,x_base=None,z0=0.0,label="Fin"):
    if x_base is None: x_base=P["nose_len"]+P["mid_len"]+P["rear_len"]-300.0
    p1=App.Vector(x_base,0,z0); p2=App.Vector(x_base+base,0,z0); p3=App.Vector(x_base,0,z0+h)
    wire=Part.makePolygon([p1,p2,p3,p1]); face=Part.Face(wire)
    fin=face.extrude(App.Vector(0,thickness,0))
    fin.Placement=App.Placement(App.Vector(0,-thickness/2.0,0),App.Rotation())
    return add_obj(fin,label)
fin=make_fin(P["fin_h"],P["fin_base"],x_base=P["nose_len"]+P["mid_len"]+200.0,label="Fin_Vertical"); set_mat(fin,'AL')

# ========================
# Radiadores imprimibles (sólidos con espesor RAD["th"])
# ========================
rads=[]
if RAD["x_start"] is None:
    RAD["x_start"] = P["nose_len"] + 300.0
if RAD["gap_x"] is None:
    RAD["gap_x"] = max(220.0, P["rad_panel_w"]*0.25)

for i in range(P["rad_panel_n"]):
    x = RAD["x_start"] + i*RAD["gap_x"]
    # derecho (+Y)
    rad_r = Part.makeBox(RAD["th"], P["rad_panel_w"], P["rad_panel_h"])
    rad_r.Placement = App.Placement(App.Vector(x, P["mid_d"]/2.0 + RAD["mount_gap_y"], -P["rad_panel_h"]/2.0), App.Rotation())
    rads.append(add_obj(rad_r, f"Radiator_R_{i+1}"))
    set_mat(rads[-1],'AL')
    # izquierdo (-Y)
    rad_l = Part.makeBox(RAD["th"], P["rad_panel_w"], P["rad_panel_h"])
    rad_l.Placement = App.Placement(App.Vector(x, -(P["mid_d"]/2.0 + RAD["mount_gap_y"] + P["rad_panel_w"]), -P["rad_panel_h"]/2.0), App.Rotation())
    rads.append(add_obj(rad_l, f"Radiator_L_{i+1}"))
    set_mat(rads[-1],'AL')

# ========================
# Compuestos por módulos para impresión/FEM
# ========================
front_parts = [nose, TPS_fused]  # Morro + TPS montado
center_parts = [mid, hull_cut, cockpit] + rads + [wing_r, wing_l, fin, tank1, tank2]
rear_parts = [rear, reactor, rings_obj, coils_obj, mod_obj, tw_obj, (nozzle_mount if 'nozzle_mount' in globals() else noz_obj), tn_obj, truss_obj,
              leg_r, leg_l, leg_r2, leg_l2, leg_f]

front_comp = Part.Compound([o.Shape for o in front_parts if hasattr(o,'Shape')])
center_comp= Part.Compound([o.Shape for o in center_parts if hasattr(o,'Shape')])
rear_comp  = Part.Compound([o.Shape for o in rear_parts if hasattr(o,'Shape')])

front_obj = add_obj(front_comp, "Module_Front_TPS")
center_obj= add_obj(center_comp,"Module_Center_Bus")
rear_obj  = add_obj(rear_comp,  "Module_Rear_Propulsion")

# Compuesto total no fusionado (para vista general)
full_comp = Part.Compound([front_obj.Shape, center_obj.Shape, rear_obj.Shape])
add_obj(full_comp, "Assembly_Compound")

doc.recompute()
print("Modelo con TPS Parker, radiadores sólidos y módulos listo. Para imprimir: exporta cada módulo por separado.")
